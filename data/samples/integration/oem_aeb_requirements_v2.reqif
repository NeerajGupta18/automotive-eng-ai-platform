# OEM AEB system requirements v2
Synthetic example of an OEM system requirement specification for AEB, version 2.

# Specification: AEB system requirements

## CR-AEB-01: Operating speed range
The AEB function shall initiate autonomous braking for vehicle speeds between 10 km/h and 85 km/h and shall warn the driver above 85 km/h.
- Verification method: Test
- Priority: High

## CR-AEB-02: Stationary vehicle ahead
The AEB function shall avoid a collision with a stationary passenger car ahead for vehicle speeds up to 50 km/h on a dry road.
- Verification method: Test
- Priority: High

## CR-AEB-03: Warning before braking
The forward collision warning shall be given at least 1.2 s before autonomous braking starts.
- Verification method: Test
- Priority: Medium

## CR-AEB-04: Robustness to false detections
Radar detections shorter than 100 ms without a real object shall not lead to a warning or to autonomous braking.
- Verification method: Test
- Priority: High

## CR-AEB-05: Driver braking
The brake request of the AEB function shall never reduce the deceleration requested by the driver.
- Verification method: Test
- Priority: High

## CR-AEB-07: Stationary two-wheeler ahead
The AEB function shall avoid a collision with a stationary motorcycle or scooter ahead for vehicle speeds up to 40 km/h.
- Verification method: Test
- Priority: High
